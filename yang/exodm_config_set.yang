submodule exodm_config_set {

  belongs-to "exodm" {
    prefix exodm;
  }

  import ietf-inet-types {
    prefix inet;
  }
  import exosense {
    prefix exo;
  }
  import exodm_type {
    prefix exodm_type;
  }
    
  description 
      "API for Exosense Device Management Server - Config Sets. " +
      "(C) 2013 Feurelabs, Inc - All Rights Reserved.";

  contact "ulf.wiger@feuerlabs.com";
  organization "Feuerlabs, Inc.";


  rpc create-config-set {
    description "Create device config data set.";
    input {
      leaf name {
        description "Name of the config data set.";
        type exodm_type:id-string; 
        mandatory true;
      }
      leaf yang {
        description "Name of the corresponding yang file - must exist.";
        type exodm_type:id-string;
        mandatory true;
      }
      leaf account {
        description "The account to which the config set belongs.";
        type exodm_type:id-string;
      }
      leaf notification-url {
        description "Notification URL.";
        type inet:uri;
      }
      anyxml values {
        description "Configuration values (validated against the yang spec).";
      }
    }

    output {
      leaf result {
        type exodm_type:result-code;
      }
    }
  }

  rpc update-config-set {
    description "Updates existing config data set.";
    input {
      leaf name {
        description "Name of the config data set.";
        type exodm_type:id-string;
        mandatory true;
      }
      leaf account {
        description "The account to which the config set belongs.";
        type exodm_type:id-string;
      }
      leaf notification-url {
        description "Notification URL.";
        type inet:uri;
      }
      anyxml values {
        description
          "Configuration values (validated against the yang spec).";
      }
    }

    output {
      leaf result {
        type exodm_type:result-code;
      }
    }
  }

  rpc delete-config-set {
    description
      "Delete a config data set. Any member devices must first be removed.";
    input {
      leaf name {
        description "Name of the config data set.";
        type exodm_type:id-string;
        mandatory true;
      }
      leaf account {
        description "The account to which the config set belongs.";
        type exodm_type:id-string;
      }
    }

    output {
      leaf result {
        type exodm_type:result-code;
      }
    }
  }

  rpc list-config-sets {
    description "List config sets, N entries at a time.";

    input {
      leaf n {
        description "Number of entries to fetch.";
        type uint32;
        mandatory true;
      }
      leaf previous {
        description "Previous config set; \"\" if from beginning.";
        type exodm_type:id-string;
        mandatory true;
      }
      leaf account {
        description "The account to which the config set belongs.";
        type exodm_type:id-string;
      }
      leaf device-id {
        description
          "Optional device ID. If given, config specs associated with " +
          "the given device are listed.";
        type exodm_type:id-string;
      }
    }
    output {
      leaf result {
        type exodm_type:result-code;
      }
      list config-sets {
        leaf name {
          type exodm_type:id-string;
        }
        leaf yang {
          type string;
        }
        leaf notification-url {
          type inet:uri;
        }
      }
    }
  }

  rpc list-config-set-members {
    description "List members of a config set, N entries at a time.";

    input {
      leaf name {
        description "Name of the config set.";
        type exodm_type:id-string;
        mandatory true;
      }
      leaf n {
        description "Number of entries to fetch.";
        type uint32;
        mandatory true;
      }
      leaf previous {
        description "Previous member; \"\" if from beginning.";
        type exodm_type:id-string;
        mandatory true;
      }
      leaf account {
        description "The account to which the config set belongs.";
        type exodm_type:id-string;
      }
    }
    output {
      leaf result {
        type exodm_type:result-code;
      }
      leaf-list config-set-members {
        description "";
        type exodm_type:id-string;
      }
    }
  }

  rpc add-config-set-members {
    description
      "Add a device to a config set.";
    input {
      leaf-list name {
        description
          "Configuration data instances to associate with " +
          "the given device(s).";
        type exodm_type:id-string;
      }
      leaf-list device-id {
        description
          "Devices to push the given config data instances to.";
        type exodm_type:id-string;
      }
      leaf account {
        description "The account to which the config set belongs.";
        type exodm_type:id-string;
      }
    }

    output {
      leaf result {
        type exodm_type:result-code;
      }
    }
  }

  rpc remove-config-set-members {
    description
      "Remove a config set member.";
    input {
      leaf-list name {
        description
          "Configuration data instances from which to remove " +
          "the given devices.";
        min-elements 1;
        type exodm_type:id-string;
      }
      leaf-list device-id {
        description
          "Devices to remove from the given config data instances.";
        min-elements 1;
        type exodm_type:id-string;
      }
      leaf account {
        description "The account to which the config set belongs.";
        type exodm_type:id-string;
      }
    }
    output {
      leaf result {
        type exodm_type:result-code;
      }
    }
  }

  rpc read-config-set-data {
    description
      "Reads the user data stored in a config set.";
    input {
      leaf name {
        description "Name of the config data set.";
        type exodm_type:id-string;
        mandatory true;
      }
      leaf area {
	description "Type of data area to read from";
	type enumeration {
	  enum staged;
	  enum pending;
	  enum installed;
	}
      }
      leaf account {
        description "The account to which the config set belongs.";
        type exodm_type:id-string;
      }
    }

    output {
      leaf result {
        type exodm_type:result-code;
      }
      anyxml values;
    }
  }


  rpc push-config-set {
    description "Push the given configuration data to all member devices.";
    exo:matching-notification "push-config-set-callback";
    input {
      leaf account {
        description "The account to which the config set belongs.";
        type exodm_type:id-string;
      }
      leaf name {
        description "Name of configuration data set to push.";
        type exodm_type:id-string;
      }
    }

    output {
      leaf result {
        type exodm_type:result-code;
      }
    }
  }

  notification push-config-set-callback {
    uses exo:std-callback;
  }

  rpc add-notification-urls {
    description "Add device-specific ConfigSet+URL pairs";
    input {
      leaf device-id {
	type exodm_type:id-string;
	mandatory true;
      }
      list urls {
	leaf config-set {
	  type exodm_type:id-string;
	}
	leaf notification-url {
	  type inet:uri;
	}
      }
    }
    output {
      leaf result {
	type exodm_type:result-code;
      }
    }
  }
  
  rpc delete-notification-urls {
    description "Remove device-specific ConfigSet+URL pairs";
    input {
      leaf device-id {
	type exodm_type:id-string;
	mandatory true;
      }
      leaf-list config-sets {
	type exodm_type:id-string;
      }
    }
    output {
      leaf result {
	type exodm_type:result-code;
      }
    }
  }
}
