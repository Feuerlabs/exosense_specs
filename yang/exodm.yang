// ---- BEGIN COPYRIGHT ---------------------------------------------
//
// Copyright © 2012 Feuerlabs, Inc. All rights reserved.
//
// This Source Code Form is subject to the terms of the Mozilla
// Public License, v. 2.0. If a copy of the MPL was not distributed
// with this file, You can obtain one at http://mozilla.org/MPL/2.0/.
//
// ---- END COPYRIGHT -----------------------------------------------
module exodm {
    namespace "http://feuerlabs.com/exodm";

    prefix exodm;


    // Do NOT remove
    // Needed when parsing submodules for extension handling !!!
    import ietf-inet-types {
      prefix inet;
    }
    import exosense {
      prefix exo;
    }
    import exodm_type {
      prefix exodm_type;
    }

    include exodm_user;
    include exodm_account;
    include exodm_device;
    include exodm_device_group;
    include exodm_device_type;
    include exodm_config_set;
    include exodm_yang_module;
    include exodm_package;


    description 
      "API for Exosense Device Management Server - Core aggregator. " +
      "(C) 2013 Feurelabs, Inc - All Rights Reserved.";

    contact "ulf.wiger@feuerlabs.com";
    organization "Feuerlabs, Inc.";

    revision 2013-01-23 {
      description
	"Split into several files";
    }
    revision 2012-11-30 {
      description
	"Added device-type definitions; harmonized ID string lengths, " +
	"some cleanups to stay within 80 char line lengths.";
    }
    revision 2012-10-26 {
      description "Validation and cleanup";
    }

}
