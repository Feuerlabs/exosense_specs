submodule exodm_account {

  belongs-to "exodm" {
    prefix "exodm";
  }

  import exodm_type {
    prefix exodm_type;
  }


  description 
      "API for Exosense Device Management Server - Account Management. " +
      "(C) 2013 Feurelabs, Inc - All Rights Reserved.";

  contact "ulf.wiger@feuerlabs.com";
  organization "Feuerlabs, Inc.";

  rpc create-account {
    description "Creates a new account.";
    input {
      leaf name { type exodm_type:id-string; mandatory true; }
      uses exodm_type:user-obj {
        refine uname {mandatory false;}
      }
    }
    output {
      leaf result { type exodm_type:result-code; }
      leaf account-admin { type exodm_type:id-string; }
    }
  }

  rpc update-account {
    description
      "Update account information.";
    input {
      leaf name {
        description "The account name.";
        type exodm_type:id-string;
      }
    }

    output {
      leaf result {
        type exodm_type:result-code;
      }
    }
  }

  rpc delete-account {
    description
      "Delete an account,
	   data must be deleted before account is removed.";
    input {
      leaf name {
        description "The account name.";
        type exodm_type:id-string;
        mandatory true;        
      }
    }
      
    output {
      leaf result {
        type exodm_type:result-code;
      }
    }	
  }
  
  rpc lookup-account {
    description
      "Read a single account.";
    input {
      leaf name {
        type exodm_type:id-string;
        mandatory true;
      }
    }
    output {
      leaf result {
        type exodm_type:result-code;
      }
      leaf-list accounts {
        description "A list of zero or one accounts.";
        type exodm_type:id-string;
      }
    }
  }
  
  rpc list-accounts {
    description "List all account names.";
    input {
      leaf n {
        description "Number of entries to fetch.";
        type uint32;
        mandatory true;        
      }
      leaf previous {
        description 'Previous account name; "" if from beginning.';
        type exodm_type:id-string;
        mandatory true;        
      }
    }
    output {
      leaf result {
        type exodm_type:result-code;
      }
      leaf-list accounts {
        description "List of account ID.";
        type exodm_type:id-string;
      }
    }
  }
  rpc add-account-users {
    description "Add account access to existing user(s)." +
      "Predefined roles are: admin, config, execute, view.";
    input {
      leaf "account" { type exodm_type:id-string; mandatory true; }
      leaf "role" { type exodm_type:id-string; mandatory true; }
      leaf-list unames { 
        description
          "Users to add to account.";
        min-elements 1;
        max-elements 10;
        type exodm_type:id-string; 
      }
    }    
    output {
      leaf result { type exodm_type:result-code; }
    }
  }

  rpc remove-account-users {
    description "Remove account access from existing user(s).";
    input {
      leaf "account" { type exodm_type:id-string; mandatory true; }
      leaf "role" { type exodm_type:id-string; mandatory true; }
      leaf-list unames { 
        description
          "Users to remove from account.";
        min-elements 1;
        max-elements 10;
        type exodm_type:id-string; 
      }
    }
    output {
      leaf result { type exodm_type:result-code; }
    }
  }

  rpc remove-account-user {
    description "Remove all account access from existing user.";
    input {
      leaf "account" { type exodm_type:id-string; mandatory true; }
      leaf "uname" { type exodm_type:id-string; mandatory true; }
    }
    output {
      leaf result { type exodm_type:result-code; }
    }
  }

  rpc list-account-users {
    description "List all users with access to account.";
    input {
      leaf "account" { 
        type exodm_type:id-string;
        mandatory true;        
      }
      leaf n {
        description "Number of entries to fetch.";
        type uint32;
        mandatory true;        
      }
      leaf previous {
        description 'Previous user name; "" if from beginning.';
        type exodm_type:id-string;
        mandatory true;        
      }
      leaf direction {
        description "Search direction.";
        type exodm_type:direction;
        default ascending;
      }
    }
    output {
      leaf result {
        type exodm_type:result-code;
      }
      list users {
        leaf name {
          description "List of user names."; 
          type exodm_type:id-string;
        }
        leaf-list roles {
          description "List of role names."; 
          type exodm_type:id-string;
        }
      }
    }
  }

  rpc list-account-roles {
    description "List all roles defined for account.";
    input {
      leaf "account" { 
        type exodm_type:id-string;
        mandatory true;        
      }
      leaf n {
        description "Number of entries to fetch.";
        type uint32;
        mandatory true;        
      }
      leaf previous {
        description 'Previous user name; "" if from beginning.';
        type exodm_type:id-string;
        mandatory true;        
      }
    }
    output {
      leaf result {
        type exodm_type:result-code;
      }
      leaf-list roles {
        description "List of role names."; 
        type exodm_type:id-string;
      }
    }
  }

  rpc set-mblox-parameters {
    description "Set access parameters for the push service Mblox.com";
    input {
      leaf "account" { type exodm_type:id-string; mandatory true; }

      leaf application-id {
	mandatory true;
	type string;
      }
      leaf originating-msisdn {
	mandatory true;
	type string;
      }
      leaf consumer-key {
	mandatory true;
	type string;
      }
      leaf secret-key {
	mandatory true;
	type string;
      }
      leaf token {
	mandatory false;
	type string;
      }
    }
    output {
      leaf result { type exodm_type:result-code; }
    }
  }

  rpc get-mblox-parameters {
    description "Get mblox access parameters (except the secret key)";
    input {
      leaf "account" { type exodm_type:id-string; mandatory true; }
    }
    output {
      leaf result { type exodm_type:result-code; }

      leaf application-id {
	type string;
      }
      leaf originating-msisdn {
	type string;
      }
      leaf consumer-key {
	type string;
      }
      leaf token {
	type string;
      }
    }
  }

  rpc delete-mblox-parameters {
    description "Delete mblox access parameters for account";
    input {
      leaf "account" { type exodm_type:id-string; mandatory true; }
    }
    output {
      leaf result { type exodm_type:result-code; }
    }
  }
}
