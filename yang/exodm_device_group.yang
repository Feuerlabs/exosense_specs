submodule exodm_device_group {

  belongs-to "exodm" {
    prefix exodm;
  }

  import ietf-inet-types {
    prefix inet;
  }
  import exodm_type {
    prefix exodm_type;
  }

  description 
      "API for Exosense Device Management Server - Device Type Management " +
      "(C) 2013 Feurelabs, Inc - All Rights Reserved.";

  contact "ulf.wiger@feuerlabs.com";
  organization "Feuerlabs, Inc.";

  // INTERNAL INFO!
  // <uid>/groups/<group-id>/name
  // <uid>/groups/<group-id>/url
  //
  list groups {
    description "Device group information.";

    key "group-id";

    leaf group-id {
      description "group id";
      type exodm_type:id-string;
    }

    leaf name {
      type string;
    }

    leaf notification-url {
      description "Where to send notifications.";
      type inet:uri;
    }
  }


  rpc create-device-group {
    description "Creates a device group.";

    input {
      leaf name {
        description "Group name.";
        type exodm_type:id-string;
        mandatory true;
      }
      leaf notification-url {
        description "RPC callback notification URL.";
        type inet:uri;
        mandatory true;
      }
      leaf account {
        description "The account to which the group belongs.";
        type exodm_type:id-string;
      }
    }

    output {
      leaf result {
        type exodm_type:result-code;
      }
    }
  }

  rpc delete-device-group {
    description "Deletes a device group.";

    input {
      leaf group-id {
        description "Group ID.";
        type exodm_type:id-string;
        mandatory true;
      }
       leaf account {
        description "The account to which the group belongs.";
        type exodm_type:id-string;
      }
   }

    output {
      leaf result {
        type exodm_type:result-code;
      }
    }
  }

 
  rpc list-device-groups {
    description "List device groups, N entries at a time.";

    input {
      leaf n {
        description "Number of entries to fetch.";
        type uint32;
        mandatory true;
      }
      leaf previous {
        description
          "Previous device group-id; \"\" if from beginning.";
        type exodm_type:id-string;
        mandatory true;
      }
      leaf account {
        description "The account to which the yang module belongs.";
        type exodm_type:id-string;
      }
      leaf device-id {
        description
          "Optional device ID. If given, device groups associated with " +
          "the given device are listed.";
        type exodm_type:id-string;
      }
    }
    output {
      leaf result {
        type exodm_type:result-code;
      }
      list device-groups {
        leaf group-id {
          type exodm_type:id-string;
        }
        leaf notification-url {
          type inet:uri;
        }
      }
    }
  }


  rpc list-device-group-members {
    description "List devices attached to a device group, " +
      "N entries at a time.";

    input {
      leaf group-id {
        description "ID of the device group.";
        type exodm_type:id-string;
        mandatory true;
      }
      leaf n {
        description "Number of entries to fetch.";
        type uint32;
        mandatory true;
      }
      leaf previous {
        description "Previous device; \"\" if from beginning.";
        type exodm_type:id-string;
         mandatory true;
     }
      leaf account {
        description "The account to which the group belongs.";
        type exodm_type:id-string;
      }
    }
    output {
      leaf result {
        type exodm_type:result-code;
      }
      leaf-list device-group-members {
        description "";
        type exodm_type:id-string;
      }
    }
  }


  rpc add-device-group-members {
    description "Link devices to device groups.";
    input {
      leaf-list group-id {
        description
          "Device groups to associate with the given device(s).";
        type exodm_type:id-string;
      }
      leaf-list device-id {
        description "List of Device ID(s).";
        type exodm_type:id-string;
      }
      leaf account {
        description "The account to which the group belongs.";
        type exodm_type:id-string;
      }
    }

    output {
      leaf result {
        type exodm_type:result-code;
      }
    }
  }

  rpc remove-device-group-members {
    description "Unlink devices from device groups.";
    input {
      leaf-list group-id {
        description
          "Device groups to unlink the given device(s) from.";
        min-elements 1;
        type exodm_type:id-string;
      }
      leaf-list device-id {
        description "List of device ID(s).";
        min-elements 1;
        type exodm_type:id-string;
      }
      leaf account {
        description "The account to which the group belongs.";
        type exodm_type:id-string;
      }
    }
    output {
      leaf result {
        type exodm_type:result-code;
      }
    }
  }


  rpc update-device-group {
    description "Changes the notification URL of an existing group.";

    input {
      leaf group-id {
        description "Group identifier.";
        type exodm_type:id-string;
        mandatory true;
      }
      leaf notification-url {
        description "RPC callback notification URL.";
        type inet:uri;
        mandatory true;
      }
      leaf account {
        description "The account to which the group belongs.";
        type exodm_type:id-string;
      }
    }

    output {
      leaf result {
        type exodm_type:result-code;
      }
    }
  }
}
