submodule exodm_device {
  belongs-to "exodm" {
    prefix exodm;
  }

  import exosense {
    prefix exo;
  }
  import exodm_type {
    prefix exodm_type;
  }

  description 
      "API for Exosense Device Management Server - Device Management " +
      "(C) 2013 Feurelabs, Inc - All Rights Reserved.";

  contact "ulf.wiger@feuerlabs.com";
  organization "Feuerlabs, Inc.";


  grouping device-obj {
    description "Device object leafs.";

    leaf device-id {
      description "Account-wide unique device-id.";
      type exodm_type:id-string;
      mandatory true;
    }
    leaf device-type {
      description "Type of device.";
      type exodm_type:id-string;
      mandatory true;
    }
    leaf description {
      description "User-provided description of device.";
      type string;
    }
    leaf server-key {
      description "Server key.";
      type uint64;
    }
    leaf device-key {
      description "Device key.";
      type uint64;
    }
    leaf session-timeout {
      description
        "Time of inactivity before a connected device considered off-line " +
        "(seconds; 0 seconds means no timeout).";
      type uint32 {
        range "0..43200";  // 1 sec - 12 hours
      }
      default 0;
    }
    leaf msisdn {
      type string;
    }
    leaf imsi {
      type string;
    }
    leaf imei {
      type string;
    }
    leaf latitude {
      description "Latitude of device location.";
      type decimal64 {
        fraction-digits 6;
        range "-90..90";
      }
    }
    leaf longitude {
      description "Longitude of device location.";
      type decimal64 {
        fraction-digits 6;
        range "-180..180";
      }
    }
  }

  // INTERNAL INFO!
  // <uid>/devices/<did>/name    = string()
  // <uid>/devices/<did>/msisdn  = msisdn()
  // <uid>/devices/<did>/imsi    = imsi()
  // <uid>/devices/<did>/imei    = imei()
  // <uid>/devices/<did>/__ck    = uint64()
  // <uid>/devices/<did>/__sk    = uint64()
  // <uid>/devices/<did>/groups[1]/__gid = uint32()
  //
  list devices {
    description "Device information.";
    key "did";

    leaf did {
      description "Device identifer.";
      // internally it must be escaped!
      type exodm_type:id-string;
    }

    leaf name {
      description "Optional device name.";
      type string;
    }

    list groups {
      description "Device group member ship.";
      key "id";

      leaf id {
        description "access index";
        type uint32;
      }

      leaf __gid {
        description "group id";
        type uint32;
      }
    }

    leaf msisdn {
      description "phone number used to access device if any.";
      type string;
    }

    leaf imsi {
      description "simcard identity, used to sign some data.";
      type string;
    }

    leaf imei {
      description "modem identity number";
      type string;
    }

    leaf __ck {
      description "device key";
      type uint64;
    }

    leaf __sk {
      description "server key";
      type uint64;
    }

  }

  rpc create-device {
    description
      "Create a new device. " +
      "augment this call if you want to add device-data.";
    input {
      uses device-obj;
      leaf account {
        description "The account to which the device belongs.";
        type exodm_type:id-string;
      }
    }

    output {
      leaf result {
        type exodm_type:result-code;
      }
    }
  }

  rpc update-device {
    description "Update an existing device object.";
    input {
      uses device-obj {
        refine device-type {
          mandatory false;
        }
      }
      leaf account {
        description "The account to which the device belongs.";
        type exodm_type:id-string;
      }
    }
    output {
      leaf result {
        type exodm_type:result-code;
      }
    }
  }

  rpc lookup-device {
    description
      "Read a single device object." +
      "Returns a list of zero or one device object.";
    input {
      leaf device-id {
        type exodm_type:id-string;
        mandatory true;
      }
      leaf account {
        description "The account to which the device belongs.";
        type exodm_type:id-string;
      }
    }
    output {
      leaf result {
        type exodm_type:result-code;
      }
      list devices {
        uses device-obj;
      }
    }
  }

  rpc lookup-device-attributes {
    description
      "Read device object attributes." +
      "Returns a list of zero or one device object attributes " +
      "as specified the 'attributes' parameter.";
    input {
      leaf device-id {
        type exodm_type:id-string;
        mandatory true;
      }
      leaf-list attributes {
        description
          "Available attributes are those in device-obj and " +
          "in addition the boolean attribute 'is-connected'.";
        type exodm_type:id-string;
        mandatory true;
      }
      leaf account {
        description "The account to which the device belongs.";
        type exodm_type:id-string;
      }
    }
    output {
      leaf result {
        type exodm_type:result-code;
      }
      list attributes {
        uses exo:configuration-entry;
      }
    }
  }

  rpc list-devices {
    description "List created devices, N entries at a time.";

    input {
      leaf n {
        description "Number of entries to fetch.";
        type uint32;
        mandatory true;
      }
      leaf previous {
        description "Previous device ID; \"\" if from beginning.";
        type exodm_type:id-string;
        mandatory true;
      }
      leaf account {
        description "The account to which the device belongs.";
        type exodm_type:id-string;
      }
    }
    output {
      leaf result {
        type exodm_type:result-code;
      }
      list devices {
        uses device-obj;
      }
    }
  }


  rpc list-devices-attributes {
    description
      "List device objects with attributes." +
      "Returns a list of zero or more device object matching "+
      "pattern, default is all, and their attributes " +
      "as specified the 'attributes' parameter.";
    input {
      leaf n {
        description "Number of entries to fetch.";
        type uint32;
        mandatory true;
      }
      leaf previous {
        description "Previous device ID; \"\" if from beginning.";
        type exodm_type:id-string;
        mandatory true;
      }
      leaf-list attributes {
        description
          "Available attributes are those in device-obj and " +
          "in addition the boolean attribute 'is-connected'.";
        type exodm_type:id-string;
        mandatory true;
      }
      leaf pattern {
        description "Pattern to match device-id against.";
        type exodm_type:id-string;
        default "*";
      }
      leaf direction {
        description "Search direction.";
        type exodm_type:direction;
        default ascending;
      }
      leaf account {
        description "The account to which the device belongs.";
        type exodm_type:id-string;
      }
    }
    output {
      leaf result {
        type exodm_type:result-code;
      }
      list devices {
        leaf device-id {
          description "Account-wide unique device-id.";
          type exodm_type:id-string;
        }
        list attributes {
          uses exo:configuration-entry;
        }
      }
    }
  }


  rpc delete-devices {
    description "Delete a set of existing devices.";

    input {
     leaf-list device-id {
        description "Account-wide unique device-id.";
        type exodm_type:id-string;
      }
       leaf account {
        description "The account to which the devices belongs.";
        type exodm_type:id-string;
      }
    }

    output {
      leaf result {
        type exodm_type:result-code;
      }
    }
  }
}
