submodule exodm_yang_module {

  belongs-to "exodm" {
    prefix exodm;
  }

  import exodm_type {
    prefix exodm_type;
  }

  description 
      "API for Exosense Device Management Server - Yang Module Management " +
      "(C) 2013 Feurelabs, Inc - All Rights Reserved.";
  contact "ulf.wiger@feuerlabs.com";
  organization "Feuerlabs, Inc.";

 
  rpc create-yang-module {
    description "Store a YANG module either in user or system space.";
    input {
     leaf repository {
        description
          "Where to store the module: Currently \"system\" or \"user\".";
        type exodm_type:id-string;
        mandatory true;
     }
      leaf name {
        description "Name, including extension, e.g. 'rfzone.yang'.";
        type exodm_type:id-string;
        mandatory true;
      }
      leaf yang-module {
        description "The actual source of the YANG module specification.";
        type string {
          length "1..100000";
        }
        mandatory true;
      }
      leaf account {
        description "The account to which the yang module belongs.";
        type exodm_type:id-string;
      }
    }
    output {
      leaf result {
        type exodm_type:result-code;
      }
    }
  }

  rpc delete-yang-module {
    description "Remove a YANG module from storage.";

    input {
      leaf repository {
        description
          "Where to delete the module: Currently \"system\" or \"user\".";
        type exodm_type:id-string;
        mandatory true;
      }
      leaf name {
        description "Name, including extension, e.g. 'rfzone.yang'.";
        type exodm_type:id-string;
        mandatory true;
      }
        leaf account {
        description "The account to which the yang module belongs.";
        type exodm_type:id-string;
      }
  }

    output {
      leaf result {
        type exodm_type:result-code;
      }
    }
  }

  rpc lookup-yang-module {
    description "Retreive a YANG module." +
      "Returns a list of zero or one yang module source files";

    input {
      leaf repository {
        description
          "Where to delete the module: Currently \"system\" or \"user\".";
        type exodm_type:id-string;
        mandatory true;
      }
      leaf name {
        description "Name, including extension, e.g. 'rfzone.yang'.";
        type exodm_type:id-string;
        mandatory true;
      }
        leaf account {
        description "The account to which the yang module belongs.";
        type exodm_type:id-string;
      }
  }

    output {
      leaf result {
        type exodm_type:result-code;
      }
      leaf-list yang-modules {
        description "A list of zero or one yang source files.";
        type string;
      }
    }
  }

  rpc list-yang-modules {
    description "List existing yang modules.";
    input {
      leaf repository {
        description "\"system\" or \"user\"; default: \"user\".";
        type exodm_type:id-string;
        default "user";
      }
      leaf n {
        description "Number of entries to fetch.";
        type uint32;
        mandatory true;
      }
      leaf previous {
        description "Previous yang filename.";
        type exodm_type:id-string;
        mandatory true;
      }
      leaf direction {
        description "Search direction.";
        type exodm_type:direction;
        default ascending;
      }
      leaf account {
        description "The account to which the yang module belongs.";
        type exodm_type:id-string;
      }
    }
    output {
      leaf result {
        type exodm_type:result-code;
      }
      leaf-list yang-modules {
        description "Yang filenames.";
        type string;
      }
    }
  }

  rpc add-execution-permission {
    description "Add execute permission for an rpc to a role in an account.";
    input {
      leaf repository {
        description
          "Where the module is: Currently \"system\" or \"user\".";
        type exodm_type:id-string;
        default "user";
      }
      leaf name {
        description "Name of module, including extension, e.g. 'rfzone.yang'.";
        type exodm_type:id-string;
        mandatory true;
      }
      leaf rpcname {
        description "Name of rpc e.g. 'config-device'.";
        type exodm_type:id-string;
        mandatory true;
      }
      leaf role {
        description "Name of role to add permission to.";
        type exodm_type:id-string;
        mandatory true;
      }
      leaf account {
        description "The account to which the permission belongs.";
        type exodm_type:id-string;
      }
    }

    output {
      leaf result {
        type exodm_type:result-code;
      }
    }
  }

  rpc remove-execution-permission {
    description "Remove execute permission for an rpc from " +
      "a role in an account.";
    input {
      leaf repository {
        description
          "Where the module is: Currently \"system\" or \"user\".";
        type exodm_type:id-string;
        default "user";
      }
      leaf name {
        description "Name of module, including extension, e.g. 'rfzone.yang'.";
        type exodm_type:id-string;
        mandatory true;
      }
      leaf rpcname {
        description "Name of rpc e.g. 'config-device'.";
        type exodm_type:id-string;
        mandatory true;
      }
      leaf role {
        description "Name of role to remove permission from.";
        type exodm_type:id-string;
        mandatory true;
      }
      leaf account {
        description "The account to which the permission belongs.";
        type exodm_type:id-string;
      }
    }

    output {
      leaf result {
        type exodm_type:result-code;
      }
    }
  }


  rpc list-execution-permission {
    input {
      leaf repository {
        description
          "Where the module is: Currently \"system\" or \"user\".";
        type exodm_type:id-string;
        default "user";
      }
      leaf modulename {
        description "Name of module, including extension, e.g. 'rfzone.yang'.";
        type exodm_type:id-string;
        mandatory true;
      }
      leaf rpcname {
        description "Name of rpc e.g. 'config-device'.";
        type exodm_type:id-string;
        mandatory true;
      }
      leaf account {
        description "The account to which the permissions belongs.";
        type exodm_type:id-string;
      }
    }

    output {
      leaf-list roles {
        description "List of role names."; 
        type exodm_type:id-string;
      }
    }
  }
}
