submodule exodm_device_type {

  belongs-to "exodm" {
    prefix exodm;
  }

  import exodm_type {
    prefix exodm_type;
  }

  description 
      "API for Exosense Device Management Server - Device Type Management " +
      "(C) 2013 Feurelabs, Inc - All Rights Reserved.";
  contact "ulf.wiger@feuerlabs.com";
  organization "Feuerlabs, Inc.";

    
  grouping device-type-obj {
    description "Device type object leafs.";
    leaf name {
      description "Account-wide unique device type name.";
      mandatory true;
      type exodm_type:id-string;
    }
    leaf protocol {
      description "Protocol between device and Exosense server.";
      mandatory true;
      type exodm_type:id-string;
    }
  }



  rpc create-device-type {
    description "Create a device type.";

    input {
      uses device-type-obj;
      leaf account {
        description "The account to which the device type belongs.";
        type exodm_type:id-string;
      }
    }

    output {
      leaf result {
        type exodm_type:result-code;
      }
    }
  }

  rpc update-device-type {
    description "Modify an existing device type.";
    input {
      uses device-type-obj {
        refine protocol {
          mandatory false;
        }
      }
      leaf account {
        description "The account to which the device type belongs.";
        type exodm_type:id-string;
      }
    }
    output {
      leaf result {
        type exodm_type:result-code;
      }
    }
  }

  rpc delete-device-type {
    description "Delete a device type";

    input {
      leaf name {
        description "Device type name.";
        type exodm_type:id-string;
        mandatory true;
      }
      leaf account {
        description "The account to which the device type belongs.";
        type exodm_type:id-string;
      }
    }

    output {
      leaf result {
        type exodm_type:result-code;
      }
    }
  }

  rpc list-device-types {
    description "List device types.";
    input {
      leaf n {
        description "Number of entries to fetch.";
        type uint32;
        mandatory true;
      }
      leaf previous {
        description 'Previous device type; "" if from beginning.';
        type exodm_type:id-string;
        mandatory true;
      }
      leaf account {
        description "The account to which the device types belongs.";
        type exodm_type:id-string;
      }
    }
    output {
      leaf result {
        type exodm_type:result-code;
      }
      list device-types {
        uses device-type-obj;
      }
    }
  }

  rpc list-device-type-members {
    description "List device IDs associated with a device type.";
    input {
      leaf name {
        description "Name of device type.";
        type exodm_type:id-string;
        mandatory true;
      }
      leaf n {
        description "Number of entries to fetch.";
        type uint32;
        mandatory true;
      }
      leaf previous {
        description 'Previous device ID; "" if from beginning.';
        type exodm_type:id-string;
        mandatory true;
      }
      leaf account {
        description "The account to which the device type belongs.";
        type exodm_type:id-string;
      }
    }
    output {
      leaf result {
        type exodm_type:result-code;
      }
      leaf-list device-type-members {
        description "Device ID.";
        type exodm_type:id-string;
      }
    }
  }
}
