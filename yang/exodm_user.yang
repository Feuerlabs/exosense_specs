submodule exodm_user {
  belongs-to "exodm" {
    prefix "exodm";
  }

  import exodm_type {
    prefix exodm_type;
  }


  description 
      "API for Exosense Device Management Server - User Management " +
      "(C) 2013 Feurelabs, Inc - All Rights Reserved.";

  contact "ulf.wiger@feuerlabs.com";
  organization "Feuerlabs, Inc.";


  rpc create-user {
    description "Create a new user.";
    input {
      uses exodm_type:user-obj;
    }
    output {
      leaf result { type exodm_type:result-code; }
    }
  }
    
  rpc delete-user {
    description "Delete an existing user.";
    input {
      leaf uname { type exodm_type:id-string; mandatory true; }
    }
    output {
      leaf result { type exodm_type:result-code; }
    }
  }
      
  rpc update-user {
    description "Update an existing user.";
    input {
      uses exodm_type:user-obj;
    }
    output {
      leaf result { type exodm_type:result-code; }
    }
  }

  rpc lookup-user {
    description
      "Read a single user object.";
    input {
      leaf uname {
        type exodm_type:id-string;
        mandatory true;
      }
    }
    output {
      leaf result {
        type exodm_type:result-code;
      }
      list users {
        description "A list of zero or one user objects.";
        uses exodm_type:user-obj;
      }
    }
  }

  rpc list-user-accounts {
    description
      "Read accounts and roles for a user.";
    input {
      leaf uname {
        type exodm_type:id-string;
        mandatory true;
      }
    }
    output {
      leaf result {
        type exodm_type:result-code;
      }
      list accounts {
        leaf name {
          description "List of account names."; 
          type exodm_type:id-string;
        }
        leaf-list roles {
          description "List of role names."; 
          type exodm_type:id-string;
        }
      }
    } 
  }

  rpc list-users {
    description "List all users.";
    input {
      leaf n {
        description "Number of entries to fetch.";
        type uint32;
        mandatory true;
      }
      leaf previous {
        description 'Previous user name; "" if from beginning.';
        type exodm_type:id-string;
        mandatory true;
      }
      leaf direction {
        description "Search direction.";
        type exodm_type:direction;
        default ascending;
      }
      leaf account {
        description "If account is given only users connected to that " +
          "account are returned.";
        type exodm_type:id-string;
      }
   }
    output {
      leaf result {
        type exodm_type:result-code;
      }
      leaf-list users {
        description "List of user names."; 
        type exodm_type:id-string;
      }
    }
  }
  
}
