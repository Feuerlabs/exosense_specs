module exodm_admin {
  namespace "http://feuerlabs.com/exodm_admin";
  prefix admin;

  import exodm {
    prefix exodm;
  }

  description "Admin API for Exosense Device Management Server";

  contact "ulf.wiger@feuerlabs.com";
  organization "Feuerlabs, Inc.";


  grouping user-obj {
    leaf uname      { type exodm:id-string; mandatory true; }
    leaf email      { type string; mandatory true; }
    leaf password   { type string; mandatory true; }
    leaf fullname   { type string; }
    leaf phone      { type string; }
    leaf skype      { type string; }
    leaf-list alias { type string; }
  }

  rpc create-user {
    description "Create a new user";
    input {
	uses user-obj;
	leaf account {
                description "The account name.";
                type exodm:id-string;
            }
    }
    output {
	leaf result { type exodm:result-code; }
    }
  }
    
  rpc delete-user {
    description "Delete an existing user";
    input {
	leaf uname      { type exodm:id-string; mandatory true; }
    }
   output {
      leaf result { type exodm:result-code; }
    }
  }
      
  rpc list-users {
      description "List all users.";
      input {
	leaf n {
	  description "Number of entries to fetch";
	  type uint32;
	}
	leaf previous {
	  description 'Previous user name; "" if from beginning';
	  type exodm:id-string;
	}
      }
      output {
	leaf-list users {
	  description "List of user names"; 
	  type exodm:id-string;
	}
      }
  }
  rpc add-user-accounts {
    description "Add account(s) to an existing user";
    input {
	leaf uname      { type exodm:id-string; mandatory true; }
	list account {
	    key "account-name";
	    min-elements 1;
	    max-elements 10;
	    leaf "account-name" { type exodm:id-string; mandatory true; }
	    leaf "role" { type exodm:id-string; mandatory true; }
	}    
    }
    output {
	leaf result { type exodm:result-code; }
    }
  }


  rpc create-account {
    description "Create a new account";
    input {
      leaf name { type exodm:id-string; mandatory true; }
      list admin-user {
	key "uname";
	min-elements 1;
	max-elements 1;
	uses user-obj;
      }
    }
    output {
      leaf result { type exodm:result-code; }
      leaf account-id { type string; }
    }
  }

  rpc update-account {
      description
	  "Update account information.";
        input {
            leaf name {
                description "The account name.";
                type exodm:id-string;
            }
        }

        output {
            leaf result {
                type exodm:result-code;
            }
        }
  }

  rpc delete-account {
        description
	  "Delete an account,
	   data must be deleted before account is removed.";
        input {
            leaf name {
                description "The account name.";
                type exodm:id-string;
            }
        }

        output {
            leaf result {
                type exodm:result-code;
            }
        }	
  }

  rpc list-accounts {
      description "List all account names.";
      input {
	leaf n {
	  description "Number of entries to fetch";
	  type uint32;
	}
	leaf previous {
	  description 'Previous account name; "" if from beginning';
	  type exodm:id-string;
	}
      }
      output {
	leaf-list accounts {
	  description "List of account ID";
	  type exodm:id-string;
	}
      }
  }
}
